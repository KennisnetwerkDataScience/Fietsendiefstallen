FME workspace horeca.fmw

Parameters:
- DestDataset_ESRISHAPE = ../data/horeca.zip   # Destination Esri Shapefile Folder
- QUERY:   # Overpass query
      area["name"="Groningen"]["admin_level"="8"] -> .g;
      (
          node["amenity"~"^cafe$|restaurant|^pub$|nightclub|bar|stripclub|biergarten|internet_cafe|fast_food|ice_cream|casino|gambling"](area.g);
          way["amenity"~"^cafe$|restaurant|^pub$|nightclub|bar|stripclub|biergarten|internet_cafe|fast_food|ice_cream|casino|gambling"](area.g);
          relation["amenity"~"^cafe$|restaurant|^pub$|nightclub|bar|stripclub|biergarten|internet_cafe|fast_food|ice_cream|casino|gambling"](area.g);
      );
      out center;
- XSLT:   # Embedded
      <xsl:stylesheet version="1.0" xmlns:xsl="http://www.w3.org/1999/XSL/Transform" xmlns:msxsl="urn:schemas-microsoft-com:xslt" exclude-result-prefixes="msxsl">
          <xsl:strip-space elements="*"/>
          <xsl:output method="xml" indent="yes"/>
      
          <xsl:template match="@* | node()">
              <xsl:copy>
                  <xsl:apply-templates select="@* | node()"/>
              </xsl:copy>
          </xsl:template>
      
          <xsl:template match="node">
               <xsl:element name="poi">
                  <xsl:element name="objectid">
                      <xsl:value-of select="@id"/>
                  </xsl:element>
                  <objecttype>node</objecttype>
                  <xsl:element name="lat">
                      <xsl:value-of select="@lat"/>
                  </xsl:element>
                  <xsl:element name="lon">
                      <xsl:value-of select="@lon"/>
                  </xsl:element>
                  <xsl:for-each select="tag">
                      <xsl:element name="{translate(@k, ':', '')}">
                          <xsl:value-of select="@v"/>
                      </xsl:element>
                  </xsl:for-each>
              </xsl:element>
          </xsl:template>
      
          <xsl:template match="way">
              <xsl:element name="poi">
                  <xsl:element name="objectid">
                      <xsl:value-of select="@id"/>
                  </xsl:element>
                  <objecttype>way</objecttype>
                  <xsl:element name="lat">
                      <xsl:value-of select="center/@lat"/>
                  </xsl:element>
                  <xsl:element name="lon">
                      <xsl:value-of select="center/@lon"/>
                  </xsl:element>
                  <xsl:for-each select="tag">
                      <xsl:element name="{translate(@k, ':', '')}">
                          <xsl:value-of select="@v"/>
                      </xsl:element>
                  </xsl:for-each>
              </xsl:element>
      
          </xsl:template>
              <xsl:template match="relation">
              <xsl:element name="poi">
                  <xsl:element name="objectid">
                      <xsl:value-of select="@id"/>
                  </xsl:element>
                  <objecttype>relation</objecttype>
                  <xsl:element name="lat">
                      <xsl:value-of select="center/@lat"/>
                  </xsl:element>
                  <xsl:element name="lon">
                      <xsl:value-of select="center/@lon"/>
                  </xsl:element>
                  <xsl:for-each select="tag">
                      <xsl:element name="{translate(@k, ':', '')}">
                          <xsl:value-of select="@v"/>
                      </xsl:element>
                  </xsl:for-each>
              </xsl:element>
          </xsl:template>
      
      </xsl:stylesheet>

Writers:
- ESRISHAPE_1: ESRISHAPE to $(DestDataset_ESRISHAPE) in EPSG:3857

Note: Deze workspace vraagt horecagelegenheden op uit OpenStreetMap. Daarbij wordt gebruikt gemaakt van de Overpass API. / Bekijk de Github repository https://github.com/FrieseWoudloper/workshop-maptime2016-overpass voor meer uitleg over de Overpass Query Language (QL). / Deze workspace lees alléén horecagelegenheden uit die / - zijn ingetekend als node, way of relation, / - zijn getagt met key amenity en één van de volgende values: cafe|restaurant|pub|nightclub|bar|stripclub|biergarten|internet_cafe|fast_food|ice_cream|casino|gambling, / - liggen binnen de gemeente Groningen.
Creator
    NUM = 1
    GEOMTYPE = Geometry Object
    CREATED -> HTTPCaller
Note: Overpass API request
HTTPCaller
    ADDITIONAL_URL_PARAMETERS = data;$(QUERY)
    TARGET_URL = http://overpass-api.de/api/interpreter?
    FOLLOW_REDIRECTS = Yes
    HTTP_METHOD = GET
    VERIFY_SSL_CERTIFICATES = Yes
    TARGET_ATTR_ENCODING = auto-detect
    SAVE_FILE = Attribute
    RESPONSE_HEADER_LIST_ATTR = _headers
    TRANSFER_TIMEOUT_LENGTH = 90
    CONNECTION_TIMEOUT_LENGTH = 60
    TARGET_ATTR = _response_body
    STATUS_CODE_ATTR = _http_status_code
    USE_COOKIES = No
    ERROR_ATTR = _error
    -> XSLTProcessor
Note: Transformeren van de API response zodat het verder verwerkt kan worden
XSLTProcessor
    CONFIGURATION_TYPE = Embedded Stylesheet
    XML_INPUT_TYPE = Attribute with XML Document
    RESULTS_TYPE = Results in Attribute
    ATTRIBUTE_XML = _response_body
    EMBEDDED_STYLESHEET = $(XSLT)
    ATTRIBUTE_RESULTS = _result
    TRANSFORMED -> XMLFragmenter
Note: Alleen amenity, name, lat, lon en objecttype worden nu 'exposed'. / Dit lijstje kun je natuurlijk uitbreiden.
XMLFragmenter
    FEATURE_TYPES_FORMAT_NAME = XML
    NEW_ATTRIBUTES = amenity name lat lon objecttype
    XML_SOURCE_TYPE = Attribute with XML document
    ATTRIBUTE_XML = _result
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    EMBEDDED_EXPRESSIONS = osm/poi
    FRAGMENTS -> VertexCreator
VertexCreator
    YVAL = @Value(lat)
    MODE_NAME = Add Point
    XVAL = @Value(lon)
    -> CoordinateSystemSetter
CoordinateSystemSetter
    COORDSYS = EPSG:4326
    -> AttributeManager
AttributeManager
    ATTR_TABLE:
      RENAME_SET_VALUE amenity > horecatype
      RENAME_SET_VALUE name > naam
      REMOVE lat
      REMOVE lon
      REMOVE xml_fragment
      REMOVE xml_id
      REMOVE xml_matched_element
      REMOVE xml_parent_id
      REMOVE xml_parent_child_pos
    -> horecagelegenheden (writer ESRISHAPE_1)
horecagelegenheden (writer ESRISHAPE_1)
    attributes: horecatype char(200), naam char(200), objecttype char(200)
