FME workspace openbareverlichting.fmw

Parameters:
- SourceDataset_CSV2 = https://ckan.dataplatform.nl/dataset/8b24358e-40ec-47fc-9d08-6fe121eaff37/resource/505507df-4b22-4d31-9f84-3ed57882457a/download/groningen.csv   # Source CSV (Comma Separated Value) File(s)
- DestDataset_ESRISHAPE = ..\data\openbareverlichting.zip   # Destination Esri Shapefile Folder

Readers:
- CSV2_1: CSV2 from $(SourceDataset_CSV2)

Writers:
- ESRISHAPE_1: ESRISHAPE to $(DestDataset_ESRISHAPE) in EPSG:3857

Note: Auteur: Anwar Ibrahim / Datum: 22-10-2017 / Versie: 0.2 / Omschrijving: / Lat/lon van OVL's omzetten naar een shape (EPSG:3857).
CSV (reader CSV2_1)
    attributes: longitude string, latitude string, mastnummer string, gemeente string
    -> VertexCreator
VertexCreator
    YVAL = @Value(latitude)
    MODE_NAME = Add Point
    XVAL = @Value(longitude)
    -> CoordinateSystemSetter
CoordinateSystemSetter
    COORDSYS = EPSG:4326
    -> openbareverlichting (writer ESRISHAPE_1)
openbareverlichting (writer ESRISHAPE_1)
    attributes: mastnummer char(254), gemeente char(254), longitude char(254), latitude char(254)
